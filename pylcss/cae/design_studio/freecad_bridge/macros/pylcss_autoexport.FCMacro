# Copyright (c) 2026 Kutay Demir.
# Licensed under the PolyForm Shield License 1.0.0. See LICENSE file for details.
#
# Loaded through Mod/PyLCSS/Init.py and InitGui.py in FreeCAD GUI and console
# processes. Exports final geometry, spreadsheet aliases, and FEM metadata
# after each document save, using the modern FreeCAD APIs.

import json
import math
import os
import traceback
from typing import Any, Dict, List

import FreeCAD
import Part


# ---------------------------------------------------------------------------
# Helpers
# ---------------------------------------------------------------------------
def _candidate_shapes(doc) -> List[Any]:
    """Export geometry roots, excluding inputs already represented by a parent.

    Bodies represent their final features. Group containers are traversed
    through their members instead of exporting their aggregate shapes, which
    can include Boolean operands. Metadata references and visibility do not
    control export.
    """
    geometry = [
        obj
        for obj in doc.Objects
        if (obj.isDerivedFrom("Part::Feature") or obj.isDerivedFrom("App::Link"))
        and getattr(obj, "Shape", None) is not None
    ]
    consumed = {child.Name for obj in geometry for child in obj.OutList}
    return [
        obj for obj in geometry if obj.Name not in consumed and not obj.Shape.isNull()
    ]


def _world_shape(obj):
    """Copy a feature's shape and apply placement inherited from its containers."""
    shape = obj.Shape.copy()
    parent_placement = obj.getGlobalPlacement().multiply(obj.Placement.inverse())
    shape.Placement = parent_placement.multiply(shape.Placement)
    return shape


def _spreadsheet_parameters(doc) -> Dict[str, float]:
    """Read finite numeric aliases, qualifying names shared by multiple sheets."""
    entries = []
    counts = {}
    for obj in doc.Objects:
        if obj.TypeId != "Spreadsheet::Sheet":
            continue
        for cell in obj.getNonEmptyCells():
            alias = obj.getAlias(cell)
            if not alias:
                continue
            counts[alias] = counts.get(alias, 0) + 1
            value = getattr(obj, cell)
            if hasattr(value, "Value"):
                value = value.Value
            if isinstance(value, (int, float)) and not isinstance(value, bool):
                value = float(value)
                if math.isfinite(value):
                    entries.append((obj.Name, alias, value))
    return {
        (sheet + "." + alias if counts[alias] > 1 else alias): value
        for sheet, alias, value in entries
    }


def _fem_analysis_summary(doc) -> List[Dict[str, Any]]:
    """Collect FEM constraint/load definitions if a Fem::FemAnalysis container
    exists. Returns an empty list otherwise so PyLCSS can ignore the section.
    """
    out: List[Dict[str, Any]] = []
    for obj in doc.Objects:
        if not obj.TypeId.startswith("Fem::"):
            continue
        if not obj.TypeId.startswith("Fem::Constraint") and not obj.TypeId.endswith(
            "Analysis"
        ):
            continue
        entry: Dict[str, Any] = {
            "name": obj.Name,
            "label": obj.Label,
            "type_id": obj.TypeId,
        }
        # Best-effort introspection: surface scalar properties + references.
        for prop_name in obj.PropertiesList:
            try:
                val = getattr(obj, prop_name)
            except Exception:
                continue
            if isinstance(val, (int, float, bool, str)):
                entry[prop_name] = val
            elif hasattr(val, "Value"):
                try:
                    entry[prop_name] = float(val.Value)
                except Exception:
                    pass
            elif prop_name in ("References", "Support") and isinstance(
                val, (list, tuple)
            ):
                references = []
                for ref in val:
                    if not isinstance(ref, (list, tuple)) or not ref:
                        continue
                    target = ref[0]
                    subelements = ref[1] if len(ref) > 1 else []
                    if isinstance(subelements, str):
                        subelements = [subelements]
                    references.append(
                        {
                            "object": getattr(target, "Name", str(target)),
                            "label": getattr(target, "Label", ""),
                            "subelements": [str(name) for name in (subelements or [])],
                        }
                    )
                if references:
                    entry["references"] = references
        out.append(entry)
    return out


# ---------------------------------------------------------------------------
# Save observer
# ---------------------------------------------------------------------------
class _PyLcssExportObserver:
    """FreeCAD document observer exporting geometry and metadata after saves."""

    def slotFinishSaveDocument(self, doc, file):  # noqa: N802 -- FreeCAD API name (1.x).
        try:
            self._export(doc)
        except Exception:
            FreeCAD.Console.PrintError(
                "[PyLCSS auto-export] failed:\n" + traceback.format_exc() + "\n"
            )

    def _export(self, doc) -> None:
        if not doc.FileName:
            return
        base, _ = os.path.splitext(doc.FileName)
        brep_path = base + ".brep"
        json_path = base + ".fcmeta.json"

        shapes = _candidate_shapes(doc)
        if not shapes:
            FreeCAD.Console.PrintMessage(
                "[PyLCSS auto-export] no exportable shapes; skipping BREP.\n"
            )
            sidecar = {
                "version": 1,
                "fcstd": doc.FileName,
                "shapes": [],
                "parameters": _spreadsheet_parameters(doc),
                "fem": _fem_analysis_summary(doc),
                "note": "no shapes detected",
            }
            with open(json_path, "w", encoding="utf-8") as fh:
                json.dump(sidecar, fh, indent=2)
            # Do not leave a previous solid's BREP beside an empty model.
            try:
                if os.path.isfile(brep_path):
                    os.remove(brep_path)
            except OSError:
                pass
            return

        # Compound the shapes so a single .brep round-trips the whole assembly.
        exported = [(obj, _world_shape(obj)) for obj in shapes]
        compound = Part.Compound([shape for _, shape in exported])
        compound.exportBrep(brep_path)

        sidecar = {
            "version": 1,
            "fcstd": doc.FileName,
            "brep": brep_path,
            "shapes": [
                {
                    "name": s.Name,
                    "label": s.Label,
                    "n_faces": len(shape.Faces),
                    "n_edges": len(shape.Edges),
                    "n_vertexes": len(shape.Vertexes),
                    "volume": float(shape.Volume),
                    "bbox": [
                        float(shape.BoundBox.XMin),
                        float(shape.BoundBox.YMin),
                        float(shape.BoundBox.ZMin),
                        float(shape.BoundBox.XMax),
                        float(shape.BoundBox.YMax),
                        float(shape.BoundBox.ZMax),
                    ],
                }
                for s, shape in exported
            ],
            "parameters": _spreadsheet_parameters(doc),
            "fem": _fem_analysis_summary(doc),
        }
        with open(json_path, "w", encoding="utf-8") as fh:
            json.dump(sidecar, fh, indent=2)

        FreeCAD.Console.PrintMessage(
            "[PyLCSS auto-export] wrote {0} + {1}\n".format(brep_path, json_path)
        )


# ---------------------------------------------------------------------------
# Registration -- run once at FreeCAD startup
# ---------------------------------------------------------------------------
def _install():
    if getattr(FreeCAD, "_pylcss_observer", None) is not None:
        return
    obs = _PyLcssExportObserver()
    FreeCAD.addDocumentObserver(obs)
    # Keep a strong reference so GC doesn't deregister us.
    FreeCAD._pylcss_observer = obs
    FreeCAD.Console.PrintMessage("[PyLCSS] auto-export observer installed\n")


try:
    _install()
except Exception:
    FreeCAD.Console.PrintError(
        "[PyLCSS] failed to install auto-export observer:\n"
        + traceback.format_exc()
        + "\n"
    )
